# Specification: Synthetic Polarion Spec

## HDR-1: Security (Heading)

### REQ-201: Security (Software Requirement)
The system shall encrypt data at rest.

### REQ-202: Security (Software Requirement)
The system shall audit administrator access.
